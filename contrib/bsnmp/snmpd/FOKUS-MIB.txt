--
-- Copyright (c) 2001-2003
--	Fraunhofer Institute for Open Communication Systems (FhG Fokus).
--	All rights reserved.
--
-- Author: Harti Brandt <harti@frebsd.org>
--
-- Redistribution and use in source and binary forms, with or without
-- modification, are permitted provided that the following conditions
-- are met:
-- 1. Redistributions of source code must retain the above copyright
--    notice, this list of conditions and the following disclaimer.
-- 2. Redistributions in binary form must reproduce the above copyright
--    notice, this list of conditions and the following disclaimer in the
--    documentation and/or other materials provided with the distribution.
--
-- THIS SOFTWARE IS PROVIDED BY AUTHOR AND CONTRIBUTORS ``AS IS'' AND
-- ANY EXPRESS OR IMPLIED WARRANTIES, INCLUDING, BUT NOT LIMITED TO, THE
-- IMPLIED WARRANTIES OF MERCHANTABILITY AND FITNESS FOR A PARTICULAR PURPOSE
-- ARE DISCLAIMED.  IN NO EVENT SHALL AUTHOR OR CONTRIBUTORS BE LIABLE
-- FOR ANY DIRECT, INDIRECT, INCIDENTAL, SPECIAL, EXEMPLARY, OR CONSEQUENTIAL
-- DAMAGES (INCLUDING, BUT NOT LIMITED TO, PROCUREMENT OF SUBSTITUTE GOODS
-- OR SERVICES; LOSS OF USE, DATA, OR PROFITS; OR BUSINESS INTERRUPTION)
-- HOWEVER CAUSED AND ON ANY THEORY OF LIABILITY, WHETHER IN CONTRACT, STRICT
-- LIABILITY, OR TORT (INCLUDING NEGLIGENCE OR OTHERWISE) ARISING IN ANY WAY
-- OUT OF THE USE OF THIS SOFTWARE, EVEN IF ADVISED OF THE POSSIBILITY OF
-- SUCH DAMAGE.
--
-- $Begemot: bsnmp/snmpd/FOKUS-MIB.txt,v 1.5 2004/08/06 08:47:08 brandt Exp $
--
-- Begemot private definitions and fokus root.
--
FOKUS-MIB DEFINITIONS ::= BEGIN

IMPORTS
    MODULE-IDENTITY, enterprises
	FROM SNMPv2-SMI;

fokus MODULE-IDENTITY
    LAST-UPDATED "200202050000Z"
    ORGANIZATION "Fraunhofer FOKUS, CATS"
    CONTACT-INFO
	    "		Hartmut Brandt

	     Postal:	Fraunhofer Institute for Open Communication Systems
			Kaiserin-Augusta-Allee 31
			10589 Berlin
			Germany

	     Fax:	+49 30 3463 7352

	     E-mail:	harti@frebsd.org"
    DESCRIPTION
	    "The root of the Fokus enterprises tree."
    REVISION "200202050000Z"
    DESCRIPTION
	    "Initial revision."
    ::= { enterprises 12325 }

END
