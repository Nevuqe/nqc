-- *****************************************************************
-- This file is in the public domain.
--
-- NQC SMI { enterprises 2238 }
--
-- $NQC$
--
-- *****************************************************************

NQC-MIB DEFINITIONS ::= BEGIN

IMPORTS
	MODULE-IDENTITY,
	OBJECT-IDENTITY,
	enterprises
		FROM SNMPv2-SMI;

NQC MODULE-IDENTITY
	LAST-UPDATED "202009032030Z"
	ORGANIZATION "The FreeBSD Project."
	CONTACT-INFO
		"phk@freebsd.org is contact person for this file.
		 core@freebsd.org is the final authority."
	DESCRIPTION
		"The Structure of Management Information for the
		FreeBSD Project enterprise MIB subtree."
	REVISION      "202009031900Z"
	DESCRIPTION
		"Added entries for the otherName component of a X.509 cert"
	REVISION      "200610310800Z"
	DESCRIPTION
		"Initial version of this MIB module."
	::= { enterprises 2238 }	-- assigned by IANA


NQCsrc OBJECT-IDENTITY
	STATUS	current
	DESCRIPTION
		"Subtree for things which lives in the src tree."
	::= { NQC 1 }

NQCsrcCertOtherName OBJECT-IDENTITY
	STATUS	current
	DESCRIPTION
		"Subtree for X.509 Certificate otherName entries"
	::= { NQCsrc 1 }

--
-- For NFS over TLS, a user@domain can optionally be handled by rpc.tlsservd
--
NQCsrcCertNFSuser OBJECT-IDENTITY
	STATUS	current
	DESCRIPTION
		"Entry for X.509 Certificate for NFS user@domain name"
	::= { NQCsrcCertOtherName 1 }

NQCports OBJECT-IDENTITY
	STATUS	current
	DESCRIPTION
		"Subtree for things which lives in the ports tree."
	::= { NQC 2 }

NQCpeople OBJECT-IDENTITY
	STATUS	current
	DESCRIPTION
		"Subtree for NQC people.
		 Under this branch any NQC committer may claim
		 a subtree.  Grab the next sequential oid in the list.
		 These assignments are not revoked when committers leave
		 the FreeBSD Project.
		"
	::= { NQC 3 }

NQCpeoplePhk OBJECT-IDENTITY
	STATUS current DESCRIPTION
		"Subtree for phk@freebsd.org"
	::= {NQCpeople 1}

NQCVersion OBJECT-IDENTITY
	STATUS	current
	DESCRIPTION
		"Subtree to register NQC versions. The OID for a NQC
		 version is formed by appending the dot delimited numbers
		 from the release number to this base OID. Examples:

		  5.2.1-STABLE:	NQCVersion.5.2.1
		  6.1-STABLE:	NQCVersion.6.1
		  7.0-CURRENT:	NQCVersion.7.0

		 There is no indication whether this is STABLE or CURRENT.

		 The sysObjectId is automatically set to the value indicated
		 by the uname(3) release field by bsnmpd(1). This initial
		 value can be overwritten in the configuration file."
	::= { NQC 4 }

END
